--
-- DK-TRAINING-MIB.my
-- MIB generated by MG-SOFT Visual MIB Builder Version 6.0  Build 88
-- Wednesday, September 27, 2023 at 15:40:28
--

--  DK-TRAINING-MIB.my
-- MIB generated by MG-SOFT Visual MIB Builder Version 6.0  Build 88
-- Monday, September 25, 2023 at 11:49:43
-- 

	DK-TRAINING-MIB DEFINITIONS ::= BEGIN
 
		IMPORTS
			enterprises, OBJECT-TYPE, OBJECT-IDENTITY, NOTIFICATION-TYPE			
				FROM SNMPv2-SMI;
	
	
--
-- Node definitions
--
	
--  1.3.6.1.4.1.57430
		-- 1.3.6.1.4.1.57430
		dockeer OBJECT-IDENTITY
			STATUS current
			DESCRIPTION 
				"The root of the OID sub-tree assigned to Company by the Internet
				Assigned Numbers Authority (IANA)"
			::= { enterprises 57430 }

		
-- 		
-- Node definitions
-- 
-- 1.3.6.1.4.1.57430.1
		-- 1.3.6.1.4.1.57430.1
		dockerrModule OBJECT IDENTIFIER ::= { dockeer 1 }

		
--  1.3.6.1.4.1.57430.1.1
		-- 1.3.6.1.4.1.57430.1.1
		dockeerGlobalModule OBJECT-TYPE
			SYNTAX INTEGER
			MAX-ACCESS read-only
			STATUS current
			DESCRIPTION
				"Description."
			::= { dockerrModule 1 }

		
--  1.3.6.1.4.1.57430.1.3
		-- 1.3.6.1.4.1.57430.1.3
		training OBJECT IDENTIFIER ::= { dockerrModule 3 }

		
--  1.3.6.1.4.1.57430.1.3.1
		-- 1.3.6.1.4.1.57430.1.3.1
		trainingModule OBJECT-TYPE
			SYNTAX INTEGER
			MAX-ACCESS read-only
			STATUS current
			DESCRIPTION
				"Description."
			::= { training 1 }

		
--  1.3.6.1.4.1.57430.1.3.2
		-- 1.3.6.1.4.1.57430.1.3.2
		version OBJECT-TYPE
			SYNTAX OCTET STRING
			MAX-ACCESS read-only
			STATUS current
			DESCRIPTION
				"A textual identifier of the version information for this node, 
				defaulting to the update date."
			::= { training 2 }

		
--  1.3.6.1.4.1.57430.1.3.3
		-- 1.3.6.1.4.1.57430.1.3.3
		cwd OBJECT-TYPE
			SYNTAX OCTET STRING
			MAX-ACCESS read-write
			STATUS current
			DESCRIPTION
				"This node is the textual identification of the working path. 
				The path should not be empty."
			::= { training 3 }

		
--  1.3.6.1.4.1.57430.1.3.4
		-- 1.3.6.1.4.1.57430.1.3.4
		fileTrap OBJECT IDENTIFIER ::= { training 4 }

		
--  1.3.6.1.4.1.57430.1.3.4.1
		-- 1.3.6.1.4.1.57430.1.3.4.1
		fileChange NOTIFICATION-TYPE
			OBJECTS { fileName, fileRowStatus }
			STATUS current
			DESCRIPTION 
				"This notification indicates if the file under the working path has 
				changed. This notification should be sent every time the file changes."
			::= { fileTrap 1 }

		
--  1.3.6.1.4.1.57430.1.3.5
		-- 1.3.6.1.4.1.57430.1.3.5
		fileTable OBJECT-TYPE
			SYNTAX SEQUENCE OF FileEntry
			MAX-ACCESS not-accessible
			STATUS current
			DESCRIPTION
				"An object table that displays and controls files on the working path of 
				the device. The values of all read/write objects in this table are 
				persistent upon restart/reboot."
			::= { training 5 }

		
--  1.3.6.1.4.1.57430.1.3.5.1
		-- 1.3.6.1.4.1.57430.1.3.5.1
		fileEntry OBJECT-TYPE
			SYNTAX FileEntry
			MAX-ACCESS not-accessible
			STATUS current
			DESCRIPTION
				"A set of objects that displays and controls a file."
			INDEX { fileName }
			::= { fileTable 1 }

		
		FileEntry ::=
			SEQUENCE { 
				fileName
					OCTET STRING,
				fileLen
					INTEGER,
				fileRowStatus
					INTEGER
			 }

--  1.3.6.1.4.1.57430.1.3.5.1.1
		-- 1.3.6.1.4.1.57430.1.3.5.1.1
		fileName OBJECT-TYPE
			SYNTAX OCTET STRING
			MAX-ACCESS read-only
			STATUS current
			DESCRIPTION
				"A textual description of the file name of this node. If no file name 
				is known, the value is the zero-length string."
			::= { fileEntry 1 }

		
--  1.3.6.1.4.1.57430.1.3.5.1.2
		-- 1.3.6.1.4.1.57430.1.3.5.1.2
		fileLen OBJECT-TYPE
			SYNTAX INTEGER
			MAX-ACCESS read-only
			STATUS current
			DESCRIPTION
				"A number indicating the length of the file contents"
			::= { fileEntry 2 }

		
--  1.3.6.1.4.1.57430.1.3.5.1.3
		-- 1.3.6.1.4.1.57430.1.3.5.1.3
		fileRowStatus OBJECT-TYPE
			SYNTAX INTEGER
				{
				active(1),
				notReady(3),
				createandWait(5),
				destroy(6)
				}
			MAX-ACCESS read-create
			STATUS current
			DESCRIPTION
				"active(1) : A file which can provide read and write operations. 
				notReady(3) : This file cannot be read or written. 
				createandWait(5) : A file in the creation process. 
				destroy(6) : A file which has been destroyed."
			::= { fileEntry 3 }

		
	
	END

--
-- DK-TRAINING-MIB.my
--
