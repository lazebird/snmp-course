--
-- DK-TRAINING-MIB.my
-- MIB generated by MG-SOFT Visual MIB Builder Version 6.0  Build 88
-- Tuesday, September 19, 2023 at 15:16:49
--

	DK-TRAINING-MIB DEFINITIONS ::= BEGIN
 
		IMPORTS
			dockeerModule			
				FROM DOCKEER			
			OBJECT-GROUP, NOTIFICATION-GROUP			
				FROM SNMPv2-CONF			
			Integer32, OBJECT-TYPE, MODULE-IDENTITY, NOTIFICATION-TYPE			
				FROM SNMPv2-SMI;
	
	
		-- 1.3.6.1.4.1.57430.1.1000.1
		trainingModule MODULE-IDENTITY 
			LAST-UPDATED "202309181605Z"		-- September 18, 2023 at 16:05 GMT
			ORGANIZATION 
				"Dockeer"
			CONTACT-INFO 
				"support@dockeer.com.cn"
			DESCRIPTION 
				"Used for dockeer 's MIB training course."
			REVISION "202309181623Z"		-- September 18, 2023 at 16:23 GMT
			DESCRIPTION 
				"0.1"
			::= { training 1 }

		
	
--
-- Node definitions
--
	
		-- 1.3.6.1.4.1.57430.1.1000
		training OBJECT IDENTIFIER ::= { dockeerModule 1000 }

		
		-- 1.3.6.1.4.1.57430.1.1000.2
		version OBJECT-TYPE
			SYNTAX OCTET STRING
			MAX-ACCESS read-only
			STATUS current
			DESCRIPTION
				"Training test version."
			::= { training 2 }

		
		-- 1.3.6.1.4.1.57430.1.1000.3
		cwd OBJECT-TYPE
			SYNTAX OCTET STRING
			MAX-ACCESS read-write
			STATUS current
			DESCRIPTION
				"Current working directory."
			::= { training 3 }

		
		-- 1.3.6.1.4.1.57430.1.1000.4
		fileTrap OBJECT IDENTIFIER ::= { training 4 }

		
		-- 1.3.6.1.4.1.57430.1.1000.4.1
		fileChange NOTIFICATION-TYPE
			OBJECTS { fileName, fileRowStatus }
			STATUS current
			DESCRIPTION 
				"File changed traps."
			::= { fileTrap 1 }

		
		-- 1.3.6.1.4.1.57430.1.1000.5
		fileTable OBJECT-TYPE
			SYNTAX SEQUENCE OF FileEntry
			MAX-ACCESS not-accessible
			STATUS current
			DESCRIPTION
				"Table of files in current working directory."
			::= { training 5 }

		
		-- 1.3.6.1.4.1.57430.1.1000.5.1
		fileEntry OBJECT-TYPE
			SYNTAX FileEntry
			MAX-ACCESS not-accessible
			STATUS current
			DESCRIPTION
				"File entries in current working directory."
			INDEX { fileName }
			::= { fileTable 1 }

		
		FileEntry ::=
			SEQUENCE { 
				fileName
					OCTET STRING,
				fileLen
					Integer32,
				fileRowStatus
					INTEGER
			 }

		-- 1.3.6.1.4.1.57430.1.1000.5.1.1
		fileName OBJECT-TYPE
			SYNTAX OCTET STRING
			MAX-ACCESS read-only
			STATUS current
			DESCRIPTION
				"File name."
			::= { fileEntry 1 }

		
		-- 1.3.6.1.4.1.57430.1.1000.5.1.2
		fileLen OBJECT-TYPE
			SYNTAX Integer32
			MAX-ACCESS read-only
			STATUS current
			DESCRIPTION
				"File length."
			::= { fileEntry 2 }

		
		-- 1.3.6.1.4.1.57430.1.1000.5.1.3
		fileRowStatus OBJECT-TYPE
			SYNTAX INTEGER
				{
				active(1),
				notReady(3),
				createandWait(5),
				destroy(6)
				}
			MAX-ACCESS read-create
			STATUS current
			DESCRIPTION
				"File status."
			::= { fileEntry 3 }

		
		-- 1.3.6.1.4.1.57430.1.1000.6
		trainingGroups OBJECT IDENTIFIER ::= { training 6 }

		
		-- 1.3.6.1.4.1.57430.1.1000.6.1
		trainingObjectGroup OBJECT-GROUP
			OBJECTS { version, cwd, fileName, fileLen, fileRowStatus
				 }
			STATUS current
			DESCRIPTION 
				"All training objects."
			::= { trainingGroups 1 }

		
		-- 1.3.6.1.4.1.57430.1.1000.6.2
		trainingTrapGroup NOTIFICATION-GROUP
			NOTIFICATIONS { fileChange }
			STATUS current
			DESCRIPTION 
				"All training traps."
			::= { trainingGroups 2 }

		
	
	END

--
-- DK-TRAINING-MIB.my
--
